module clixon-config {

    prefix cc;

    organization
      "Clicon / Clixon";

    contact
      "Olof Hagsand <olof@hagsand.se>";

    description
      "Clixon configuration file
       ***** BEGIN LICENSE BLOCK *****
       Copyright (C) 2009-2017 Olof Hagsand and Benny Holmgren
       
       This file is part of CLIXON

       Licensed under the Apache License, Version 2.0 (the \"License\");
       you may not use this file except in compliance with the License.
       You may obtain a copy of the License at
          http://www.apache.org/licenses/LICENSE-2.0
        Unless required by applicable law or agreed to in writing, software
       distributed under the License is distributed on an \"AS IS\" BASIS,
       WITHOUT WARRANTIES OR CONDITIONS OF ANY KIND, either express or implied.
       See the License for the specific language governing permissions and
       limitations under the License.

       Alternatively, the contents of this file may be used under the terms of
       the GNU General Public License Version 3 or later (the \"GPL\"),
       in which case the provisions of the GPL are applicable instead
       of those above. If you wish to allow use of your version of this file only
       under the terms of the GPL, and not to allow others to
       use your version of this file under the terms of Apache License version 2, 
       indicate your decision by deleting the provisions above and replace them with
       the notice and other provisions required by the GPL. If you do not delete
       the provisions above, a recipient may use your version of this file under
       the terms of any one of the Apache License version 2 or the GPL.

       ***** END LICENSE BLOCK *****";

    revision 2017-07-02 {
      description
        "Added startup config";
    }
    typedef startup_mode{
	description "Which method to boot/start clicon backend.
                     The methods differ in how they reach a running state
                     Which source database to commit from, if any.";
	type enumeration{
	    enum none{
		description "Do not touch running state
                     Typically after crash when running state and db are synched";
	    }
	    enum init{
		description "Initialize running state.
                             Start with a completely clean running state";
	    }
	    enum running{
		description "Commit running db configuration into running state
                             After reboot if a persistent running db exists";
	    }
	    enum startup{
		description "Commit startup configuration into running state
                             After reboot when no persistent running db exists";
	    }
	}
    }
    container config {
    leaf CLICON_CONFIGFILE{
    	 type string;
	 description  "Location of configuration-file for default values (this file)";
    }
    leaf CLICON_YANG_DIR {
       type string;
       mandatory true;
       description "Location of YANG module and submodule files. Only if CLICON_DBSPEC_TYPE is YANG";
    }
    leaf CLICON_YANG_MODULE_MAIN {
       type string;
       default "clicon";
       description "Option used to construct initial yang file:
                    <module>[@<revision>]
		    This option is only relevant if CLICON_DBSPEC_TYPE is YANG";
    }
    leaf CLICON_YANG_MODULE_REVISION {
       type string;
       description "Option used to construct initial yang file:
                    <module>[@<revision>]";
    }
    leaf CLICON_BACKEND_DIR {
       type string;
       description "Location of backend .so plugins. Load all .so 
                    plugins in this dir as backend plugins";
    }
    leaf CLICON_NETCONF_DIR {
       type string;
       description "Location of netconf (frontend) .so plugins";
    }
    leaf CLICON_RESTCONF_DIR {
       type string;
       description "Location of restconf (frontend) .so plugins. Load all .so
                    plugins in this dir as restconf code plugins";
    }
    leaf CLICON_RESTCONF_PATH {
       type string;
       default "/www-data/fastcgi_restconf.sock";
       description "FastCGI unix socket. Should be specified in webserver
                    Eg in nginx: fastcgi_pass unix:/www-data/clicon_restconf.sock";
    }
    leaf CLICON_CLI_DIR {
       type string;
       description "Location of cli frontend .so plugins. Load all .so 
                    plugins in this dir as CLI object plugins";
    }
    leaf CLICON_CLISPEC_DIR {
       type string;
       description "Location of frontend .cli cligen spec files. Load all .cli 
                    files in this dir as CLI specification files";
    }
    leaf CLICON_CLISPEC_FILE {
       type string;
       description "Specific frontend .cli cligen spec file.";
    }
    leaf CLICON_CLI_MODE {
       type string;
       default "base";
       description "Startup CLI mode. This should match a CLICON_MODE set in
                    one of the clispec files";
    }
    leaf CLICON_CLI_GENMODEL {
       type int32;
       default 1;
       description "Generate code for CLI completion of existing db symbols. 
                    Example: Add name=\"myspec\" in datamodel spec and reference
		    as @myspec";
    }
    leaf CLICON_CLI_GENMODEL_COMPLETION {
       type int32;
       default 1;
       description "Generate code for CLI completion of existing db symbols";
    }
    leaf CLICON_CLI_GENMODEL_TYPE {
       type string;
       default "VARS";
       description "How to generate and show CLI syntax: VARS|ALL";
    }
    leaf CLICON_CLI_VARONLY {
       type int32;
       default 1;
       description "Dont include keys in cvec in cli vars callbacks, ie a & k in 'a <b> k <c>' ignored";
    }
    leaf CLICON_CLI_LINESCROLLING {
      type int32;
      default 1;
      description "Set to 0 if you want CLI to wrap to next line.
                   Set to 1 if you  want CLI to scroll sideways when approaching right margin";
    }

    leaf CLICON_SOCK_FAMILY {
       type string;
       default "UNIX";
       description "Address family for communicating with clixon_backend (UNIX|IPv4|IPv6)";
    }
    leaf CLICON_SOCK {
       type string;
       mandatory true;
       description "If family above is AF_UNIX: Unix socket for communicating 
       		    with clixon_backend. If family is AF_INET: IPv4 address";
    }
    leaf CLICON_SOCK_PORT {
       type int32;
       default 4535;
       description "Inet socket port for communicating with clixon_backend (only IPv4|IPv6)";
    }
    leaf CLICON_SOCK_GROUP {
       type string;
       default "clicon";
       description "Group membership to access clixon_backend unix socket";
    }
    leaf CLICON_BACKEND_PIDFILE {
       type string;
       mandatory true;
       description "Process-id file";
    }
    leaf CLICON_AUTOCOMMIT {
       type int32;
       default 0;
       description "Set if all configuration changes are committed directly, 
                    commit command unnecessary";
    }
    leaf CLICON_MASTER_PLUGIN {
       type string;
       default "master";
       description "Name of master plugin (both frontend and backend). 
                    Master plugin has special callbacks for frontends. 
		    See clicon user manual for more info. (Obsolete)";
    }
    leaf CLICON_XMLDB_DIR {
       type string;
       mandatory true;
       description "Directory where \"running\", \"candidate\" and \"startup\" are placed";
    }
    leaf CLICON_USE_STARTUP_CONFIG {
       type int32;
       default 0;
       description "Enabled uses \"startup\" configuration on boot. It is called
                    startup_db and exists in XMLDB_DIR. NOTE: Obsolete with CLICON_STARTUP_MODE";
    }
    leaf CLICON_XMLDB_PLUGIN {
       type string;
       mandatory true;
       description "XMLDB datastore plugin filename (see datastore/ and clixon_xml_db.[ch])";
    }
    leaf CLICON_STARTUP_MODE {
	type startup_mode;
	description "Which method to boot/start clicon backend";
    }

  }
}
