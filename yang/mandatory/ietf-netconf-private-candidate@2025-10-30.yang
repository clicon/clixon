module ietf-netconf-private-candidate {
    yang-version 1.1;
    namespace "urn:ietf:params:xml:ns:yang:ietf-netconf-private-candidate";
    prefix pc;

    import ietf-nmda-compare {
        prefix cmp;
    }

    organization
        "IETF NETCONF (Network Configuration) Working Group";
    contact
        "WG Web:   <http://tools.ietf.org/wg/netconf/>
        WG List:  <netconf@ietf.org>

        Editor:   James Cumming
               <james.cumming@nokia.com>

        Editor:   Robert Wills
               <rowills@cisco.com>";
    description
        "NETCONF private candidate support.

        Copyright (c) <year> IETF Trust and the persons identified as
        authors of the code.  All rights reserved.

        Redistribution and use in source and binary forms, with or
        without modification, is permitted pursuant to, and subject to
        the license terms contained in, the Revised BSD License set
        forth in Section 4.c of the IETF Trust's Legal Provisions
        Relating to IETF Documents

        (https://trustee.ietf.org/license-info).

        This version of this YANG module is part of RFC XXXX
        (https://www.rfc-editor.org/info/rfcXXXX); see the RFC itself
        for full legal notices.

        The key words 'MUST', 'MUST NOT', 'REQUIRED', 'SHALL', 'SHALL
        NOT', 'SHOULD', 'SHOULD NOT', 'RECOMMENDED', 'NOT RECOMMENDED',
        'MAY', and 'OPTIONAL' in this document are to be interpreted as
        described in BCP 14 (RFC 2119) (RFC 8174) when, and only when,
        they appear in all capitals, as shown here.";

    revision 2025-10-30 {
        description
            "Introduce private candidate support";
        reference
            "draft-ietf-netconf-privcand:
             Netconf Private Candidates";
    }
    revision 2024-09-12 {
        description
            "Introduce private candidate support";
        reference
            "draft-ietf-netconf-privcand:
             Netconf Private Candidates";
    }

    feature private-candidate {
        description
            "NETCONF :private-candidate capability;
          If the server advertises the :private-candidate
          capability for a session, then this feature must
          also be enabled for that session.  Otherwise,
          this feature must not be enabled.";
        reference
            "draft-ietf-netconf-privcand";
    }

    rpc update {
        if-feature "private-candidate";
        description
            "Updates the private candidate from the running
             configuration.";
        reference
            "draft-ietf-netconf-privcand";
        input {
            leaf resolution-mode {
                type enumeration {
                    enum revert-on-conflict {
                        description
                            "Reject update when any conflicting
                             node is found and revert the private
                             candidate configuration datastore to its
                             state prior to issuing the update.";
                    }
                    enum prefer-candidate {
                        description
                            "Resolve conflicted node by selecting
                             the private candidate configuration
                             datastore version.";
                    }
                    enum prefer-running {
                        description
                            "Resolve conflicted node by selecting
                             the running configuration datastore
                             version.";
                    }
                }
                default "revert-on-conflict";
                description
                    "Mode to resolve conflicts between running and
                     private-candidate configurations.";
            }
        }
    }

    augment "/cmp:compare/cmp:input" {
        if-feature "private-candidate";
        description
            "Augment private candidate extensions into the NETCONF compare
             RPC";
        leaf reference-point {
            type enumeration {
                enum last-update {
                    description
                        "Compare using the point the private
                         candidate configuration datastore was
                         last updated using the update or commit
                         RPCs.";
                }
                enum creation-point {
                    description
                        "Compare using the point the private
                         candidate configuration datastore was
                         initially created.";
                }
            }
            default "last-update";
            description
                "When this leaf is provided and the source or
                 destination is the candidate datastore, operating
                 in private candidate mode, the comparison will
                 either occur between the last-update point of
                 the private candidate or the creation-point of
                 the private candidate.";
            reference
                "draft-ietf-netconf-privcand";
        }
    }
}
