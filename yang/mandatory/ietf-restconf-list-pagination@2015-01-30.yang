module ietf-restconf-list-pagination {
     namespace "urn:ietf:params:xml:ns:yang:ietf-restconf-list-pagination";
     prefix rlpg;
     import ietf-restconf {
       prefix rc;
     }
     organization
       "IETF NETCONF (Network Configuration) Working Group";
     contact
       "WG Web:   <http://tools.ietf.org/wg/netconf/>
        WG List:  <mailto:netconf@ietf.org>";

     description
       "This module contains conceptual YANG specifications
        for the RESTCONF Collection resource type.
        Note that the YANG definitions within this module do not
        represent configuration data of any kind.
        The YANG grouping statements provide a normative syntax
        for XML and JSON message encoding purposes.

        Copyright (c) 2015 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
        the RFC itself for full legal notices.";

     revision 2015-01-30 {
       description
         "Initial revision.";
       reference
         "RFC XXXX: RESTCONF Collection Resource.";
     }
     rc:yang-data yang-collection {
       uses collection;
     }

     grouping collection {
       description
         "Conceptual container representing the
          yang-collection resource type.";
       container yang-collection {
         description
           "Container representing the yang-collection
            resource type.";
       }
     }
}
