module clixon-clispec{
    yang-version 1.1;
    namespace "http://clicon.org/clispec";
    prefix ccli;

    organization
	"Clicon / Clixon";

    contact
	"Olof Hagsand <olof@hagsand.se>";

    description
	"Clixon CLIgen specification declarations, including autocli.
      
       ***** BEGIN LICENSE BLOCK *****
       Copyright (C) 2020-2021 Olof Hagsand and Rubicon Communications, LLC(Netgate)
       
       This file is part of CLIXON

       Licensed under the Apache License, Version 2.0 (the \"License\");
       you may not use this file except in compliance with the License.
       You may obtain a copy of the License at
            http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License.

       Alternatively, the contents of this file may be used under the terms of
       the GNU General Public License Version 3 or later (the \"GPL\"),
       in which case the provisions of the GPL are applicable instead
       of those above. If you wish to allow use of your version of this file only
       under the terms of the GPL, and not to allow others to
       use your version of this file under the terms of Apache License version 2, 
       indicate your decision by deleting the provisions above and replace them with
       the notice and other provisions required by the GPL. If you do not delete
       the provisions above, a recipient may use your version of this file under
       the terms of any one of the Apache License version 2 or the GPL.

       ***** END LICENSE BLOCK *****";

    revision 2021-12-05 {
	description
	    "Initial version";
    }
    
    grouping clixon-clispec{
	list rule {
	    description
		"Represents a modification rule of a clixon clispec.";
	    ordered-by user; /* eg modules: omit * */
	    key id;

	    leaf id {
		description
		    "Arbitrary string index for the rule";
		type string;
	    }
	    leaf description {
		description
		    "Rule description";
		type string;
	    }
	    leaf-list node-id {
		description
		    "path in the form of <id>/<id> or just a single <id> identifying a YANG
                     schema-node identifier as defined in RFC 7950 Sec 6.5
                     Example: 'config', '/interfaces/interface'";
		type string;
	    }
	    leaf-list module {
		description
		    "Constraints the rule to the module names identified by a glob.
                     Wildchars '*' and '?' can be used.
                     Revision and yang suffix are ommitted
                     Note, this special rule is necessary since node-id cannot be used for
                     modules.
                     Example: 'openconfig-*'";
		type string;
	    }
	    leaf-list yang-keyword {
		description
		    "If present identifes a YANG keyword which the rule applies to
                     Example: 'container'";
		type string;
	    }
	    leaf operation {
		type enumeration {
		    enum exclude {
			description
			    "Exclude a subtree from rendering of autocli. 
                             Example: exclude: openconfig-* module";
		    }
		    enum include {
			description
			    "Include a subtree to rendering of autocli. 
                             Example: include: openconfig-wifi module";
		    }
		    enum omit {
			description
			    "Remove a single keyword from a command. 
                             Example: replace 'interfaces interface' with 'interface' ??";
		    }
		    enum hide {
			description
			"A complete command (not just single keyword) is hidden from CLI query,
                         help and completion, ie a user must type it manually. 
                         Example: 'start shell'";
		    }
		}
	    }
	}
    }
}
