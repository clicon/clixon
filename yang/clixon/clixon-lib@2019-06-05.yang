module clixon-lib {
    yang-version 1.1;
    namespace "http://clicon.org/lib";
    prefix cl;

    organization
	"Clicon / Clixon";

    contact
	"Olof Hagsand <olof@hagsand.se>";

    description
      "Clixon Netconf extensions for communication between clients and backend.
      
       ***** BEGIN LICENSE BLOCK *****
       Copyright (C) 2009-2019 Olof Hagsand and Benny Holmgren
       
       This file is part of CLIXON

       Licensed under the Apache License, Version 2.0 (the \"License\");
       you may not use this file except in compliance with the License.
       You may obtain a copy of the License at
            http://www.apache.org/licenses/LICENSE-2.0
       Unless required by applicable law or agreed to in writing, software
       distributed under the License is distributed on an \"AS IS\" BASIS,
       WITHOUT WARRANTIES OR CONDITIONS OF ANY KIND, either express or implied.
       See the License for the specific language governing permissions and
       limitations under the License.

       Alternatively, the contents of this file may be used under the terms of
       the GNU General Public License Version 3 or later (the \"GPL\"),
       in which case the provisions of the GPL are applicable instead
       of those above. If you wish to allow use of your version of this file only
       under the terms of the GPL, and not to allow others to
       use your version of this file under the terms of Apache License version 2, 
       indicate your decision by deleting the provisions above and replace them with
       the notice and other provisions required by the GPL. If you do not delete
       the provisions above, a recipient may use your version of this file under
       the terms of any one of the Apache License version 2 or the GPL.

       ***** END LICENSE BLOCK *****";

    revision 2019-08-13 {
	description
	    "get-state added for restconf content=nonconfig internal rpc";
    }
    revision 2019-06-05 {
	description
	    "ping rpc added for liveness";
    }
    revision 2019-01-02 {
	description
	    "Released in Clixon 3.9";
    }
    import ietf-netconf {
	description "for the get-state extension";
	prefix nc;
    }

    rpc debug {
	description "Set debug level of backend.";
	input {
	    leaf level {
		type uint32;
	    }
	}
    }
    rpc ping {
        description "Check aliveness of backend daemon.";
    }
    rpc get-state {
      description
        "Retrieve device state information only. This is a clixon extension
         to ietf-netconf to implement RESTCONF GET with attribute 
         content=nonconfig. 
         The reason is that netconf only has <get> and <get-config> neither
         which retrieves state only";

      reference "RFC 8040 4.8.1";

      input {
        anyxml filter {
          description
            "This parameter specifies the portion of the system
             configuration and state data to retrieve.";
          nc:get-filter-element-attributes;
        }
      }

      output {
        anyxml data {
          description
            "Copy of the running datastore subset and/or state
             data that matched the filter criteria (if any).
             An empty data container indicates that the request did not
             produce any results.";
        }
      }
    }
}
