module clixon-hello {
    yang-version 1.1;
    namespace "urn:example:hello";
    prefix he;
    revision 2019-04-17 {
	description
	    "Clixon hello world example";
    }
    container hello{
	container world{
	    presence true;
	}
    }
}
